"""FreeCAD macro: build the BombBusters token/card/marker reference shapes.

Run inside FreeCAD 1.0.2. Reloads the project's Python modules so edits take effect
without restarting FreeCAD, recreates the document from scratch, builds the parts, and
sets an isometric, fit-all view (see the repository ``CLAUDE.md``).
"""

import importlib
import os
import sys

import FreeCAD as App
import FreeCADGui as Gui

DOC_NAME = "BombBusters"

# Make sure the project directory (this macro's folder) is importable.
try:
    _macro_dir = os.path.dirname(os.path.abspath(__file__))
except NameError:  # __file__ is undefined in some macro contexts
    _macro_dir = (
        os.path.dirname(os.path.abspath(App.ActiveDocument.FileName))
        if App.ActiveDocument
        else os.getcwd()
    )
if _macro_dir not in sys.path:
    sys.path.insert(0, _macro_dir)

# Reload config first, then the geometry module so it picks up the latest constants.
import config  # noqa: E402

importlib.reload(config)
import tokens  # noqa: E402

importlib.reload(tokens)

# Recreate the document from scratch.
if DOC_NAME in App.listDocuments():
    App.closeDocument(DOC_NAME)
doc = App.newDocument(DOC_NAME)

# Hidden on build: Tray_*/WireTray_* cutting tools (not meant to be seen),
# WireToken_Blue_* (already has its own bag -- no box planned for it), the
# box-level InfoToken/InfoMarker/EquipmentToken/BlueCutDisc originals now that
# their Tray_-prefixed counterparts are actually housed in TokenTray,
# Card_Equipment now that Card_Equipment_Double supersedes it, and
# WireStand_Void_* (the angled-side hollowing cavities -- kept as their own
# objects, hidden by default, so they can be toggled visible to check the
# hollowing against WireStand directly).
_HIDDEN_PREFIXES = (
    "Tray_",
    "WireTray_",
    "WireToken_Blue_",
    "InfoToken_",
    "InfoMarker_",
    "SecretMissionAccessCut_",
    "SecretMissionToken_",
    "WireStand_Void_",
)
_HIDDEN_NAMES = {
    "EquipmentToken_Pair",
    "BlueCutDisc_Stack",
    "Card_Equipment",
    "WireToken_Red",
    "WireToken_Yellow",
    "Card_Mission",
    "Card_Equipment_Double",
    "TokenTrayLid",
    "SecretMissionTray",
    "WireTray",
}

for name, shape in tokens.build_all():
    obj = doc.addObject("Part::Feature", name)
    obj.Shape = shape
    if obj.ViewObject is not None and (name.startswith(_HIDDEN_PREFIXES) or name in _HIDDEN_NAMES):
        obj.ViewObject.Visibility = False

box_obj = doc.addObject("Part::Feature", "Box_Reference")
box_obj.Shape = tokens.build_box()
if box_obj.ViewObject is not None:
    box_obj.ViewObject.Transparency = 80
    box_obj.ViewObject.Visibility = False

doc.recompute()

# Isometric view, fit everything.
Gui.activeDocument().activeView().viewIsometric()
Gui.SendMsgToActiveView("ViewFit")
